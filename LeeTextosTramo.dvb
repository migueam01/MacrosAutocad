Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Sub LeePuntoyDec()
    ' lee las coordenadas del tramo señalados con el puntero, los textos de nudos
    ' del dibujo en AutoCAD, luego ubica los datos en Excel
    ' requiere un archivo de Excel que guarde: Descripción y las coordenadas
    Dim Excel As Object
    Dim ExcelSheet As Object
    Dim ExcelWorkbook As Object

    Dim TextoCT As AcadText
    Dim tuberiaCad As AcadLWPolyline
    
    Dim PuntoTexto As Variant
    Dim returnPnt As Variant
    Dim CodigoPunto As String
    Dim RegresaCota As Variant
    Dim Nfila As Integer
    Dim NPuntos As Integer
    Dim Nfinal As Integer
    Dim CotaT As String
    
    ColNum = 1
    ColTramo = 2
    ColNi = 3
    ColNf = 4
    ColCaudal = 5
    ColX = 6
    ColY = 7
    ColR = 8
    colTipoTub = 9
    
    'Habilita EXCEL
    Set Excel = GetObject(, "Excel.Application")
    ' Activa archivo de Excel y la hoja de trabajo abierta.
    Set ExcelWorkbook = Excel.ActiveWorkbook
    Set ExcelSheet = Excel.ActiveSheet
    Set celdas = Excel.ActiveCell
    NFilaI = celdas.row
    
    NFilaI = InputBox("No de Fila inicial", "Datos para Excel", NFilaI, 10, 10)
    NPuntos = InputBox("No de Tramos", "Datos para Excel", 1, 10, 10)
    Nfinal = NFilaI + NPuntos - 1
   
   For i = NFilaI To Nfinal
      ThisDrawing.Utility.GetEntity TextoCT, PuntoRef, "Marcar 1er. Texto del Tramo: " & (i - NFilaI + 1)
      ExcelSheet.cells(i, ColNum).Value = i
      ExcelSheet.cells(i, ColX).Value = TextoCT.InsertionPoint(0)
      ExcelSheet.cells(i, ColY).Value = TextoCT.InsertionPoint(1)
      ExcelSheet.cells(i, ColCaudal).Value = TextoCT.TextString
      ExcelSheet.cells(i, ColR).Value = TextoCT.Rotation
      TextoCT.color = acCyan
      ThisDrawing.Utility.GetEntity TextoCT, PuntoRef, "Marcar el Texto NudoArriba: " & (i - NFilaI + 1)
      ExcelSheet.cells(i, ColNi).Value = TextoCT.TextString
      ThisDrawing.Utility.GetEntity TextoCT, PuntoRef, "Marcar el Texto NudoAbajo: " & (i - NFilaI + 1)
      ExcelSheet.cells(i, ColNf).Value = TextoCT.TextString
'      ThisDrawing.Utility.GetEntity TextoCT, PuntoRef, "Marcar el Texto Tuberia: " & (i - NfilaI + 1)
'      ExcelSheet.Cells(i, ColDatos).Value = TextoCT.TextString
      ThisDrawing.Utility.GetEntity tuberiaCad, PuntoRef, "Picar tubería"
      ExcelSheet.cells(i, colTipoTub).Value = tuberiaCad.Layer
      tuberiaCad.color = acBlue
      ExcelSheet.cells(i + 1, 1).Select
   Next i
End Sub
