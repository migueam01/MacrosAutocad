Attribute VB_Name = "FormDatosHid"
Attribute VB_Base = "0{90305F6A-F101-4C9F-99D4-6343C822D3D2}{9060CA08-464A-467D-B82E-3DC334E3D33D}"
Attribute VB_GlobalNameSpace = False
Attribute VB_Creatable = False
Attribute VB_PredeclaredId = True
Attribute VB_Exposed = False
Attribute VB_TemplateDerived = False
Attribute VB_Customizable = False
Private Sub btnAceptar_Click()
    Dim opcionDibujo As Integer
    
    opcionDibujo = CInt(txtOpcionDibujo.Text)
    If optBtnNudos.Value Then
        Call insertarDatosNudosAP(opcionDibujo)
    End If
    
    If optBtnTramos.Value Then
        Call insertarDatosTramosAP(opcionDibujo)
    End If
End Sub

Private Sub Image1_Click()
    FormAyuda.show
End Sub

Private Sub optBtnNudos_Click()
    Call habilitarFormaDibujo
End Sub

Private Sub optBtnTramos_Click()
    Call habilitarFormaDibujo
End Sub

Private Function habilitarFormaDibujo()
    txtOpcionDibujo.Enabled = True
    btnAceptar.Enabled = True
End Function

Attribute VB_Name = "Module1"
'Enviar valor de 1 para filaI cuando se va a dibujar de forma individual
Sub insertarDatosTramosAP(ByVal formaDibujo As String)
    'Inserta datos hidráulicos en tramos de tubería de agua potable
    'Toma los datos de un archivo de Excel
    'Plan Maestro Tulcán
    
    FormDatosHid.Hide
    
    Dim Excel As Object
    Dim ExcelSheet As Object
    Dim ExcelWorkbook As Object
    
    Dim textoCad As AcadText
    Dim textoNudoInicio As AcadText
    Dim textoNudoFin As AcadText
    
    Dim coordTextoGuia(0 To 2) As Double
    Dim coordTextoGuiaAux As Double
    Dim lineaP2(0 To 2) As Double
    Dim GiroCaja(0 To 2) As Double
    
'    Dim formaDibujo As String
    Dim hidraulicosVerifica, coordenadasVerifica As String
    Dim caudal, velocidad, diametro As String
    Dim longitud, material As String
    Dim nudoInicioAux, nudoFinAux As String
    Dim capaDH As String
    Dim RE, MC1, MC2, altura, salto As Double
    Dim rotaGuia As Double
    Dim filaI, filaF, fila As Integer
    
    Dim colNudoInicio, colNudoFin As Integer
    Dim colCaudal, colVelocidad, colDiametro, colLongitud As Integer
    Dim colMaterial, colTextoEste, colTextoNorte, colOrientacion As Integer
    Dim colCapa As Integer
    
    'Habilita EXCEL
    Set Excel = GetObject(, "Excel.Application")
    ' Activa archivo de Excel y la hoja de trabajo abierta.
    Set ExcelWorkbook = Excel.ActiveWorkbook
    Excel.Sheets(1).Select
    Set ExcelSheet = Excel.ActiveSheet
    Set celdas = Excel.ActiveCell
    filaI = celdas.row
    
    salto = 1.75
    RE = escala / 1000
    MC1 = -3 * RE 'Cambio 6 por 2
    MC2 = 1.5 * RE 'y 14 por 10
    altura = 1.5
    
    colNudoInicio = 12: colNudoFin = 13
    colCaudal = 15: colVelocidad = 16: colDiametro = 17: colLongitud = 18
    colMaterial = 19: colTextoEste = 20: colTextoNorte = 21: colOrientacion = 22
    colCapa = 23
    
'    formaDibujo = InputBox("Forma de dibujar" & vbCrLf & "1. Por tramos" & vbCrLf & "2. Todo", "DIBUJO TRAMOS", 1)
    If formaDibujo = 1 Then
        filaI = 1
        filaF = ThisDrawing.Utility.GetInteger("Número de tramos")
    Else
        filaI = InputBox("Fila inicio", "INICIO", filaI)
        filaF = InputBox("Fila final", "FIN", filaI + 1)
    End If
    fila = 3
'    On Error Resume Next
    
    Select Case formaDibujo
        Case 1:
            For op1 = filaI To filaF
                ThisDrawing.Utility.GetEntity textoNudoInicio, puntoRef, "<Marcar texto nudo inicio: >: "
                ExcelSheet.cells(fila, colNudoInicio).Value = textoNudoInicio.TextString
                ThisDrawing.Utility.GetEntity textoNudoFin, puntoRef, "<Marcar texto nudo fin: >: "
                ExcelSheet.cells(fila, colNudoFin).Value = textoNudoFin.TextString
                'Lee del Excel datos para ubicar los datos
                capaDH = ExcelSheet.cells(fila, colCapa)
                rotaGuia = ExcelSheet.cells(fila, colOrientacion).Value
                
                'Controlar error cuando no encuentra el dato en la búsqueda para las
                'coordenadas donde se van a insertar el texto
                'si no encuentra el dato invierte los nudos.
                'Falta controlar error si no encuentra el dato al invertir
                coordenadasVerifica = ExcelSheet.cells(fila, colTextoEste).Text
                If coordenadasVerifica = "#N/A" Then
                    ExcelSheet.cells(fila, colNudoInicio).Value = textoNudoFin.TextString
                    ExcelSheet.cells(fila, colNudoFin).Value = textoNudoInicio.TextString
                End If
                
                'Lee las coordenadas para insertar los datos hidráulicos
                coordTextoGuia(0) = ExcelSheet.cells(fila, colTextoEste).Value
                coordTextoGuia(1) = ExcelSheet.cells(fila, colTextoNorte).Value
                GiroCaja(0) = coordTextoGuia(0): GiroCaja(1) = coordTextoGuia(1)
                
                'Controlar error cuando no se encuentra el dato en la búsqueda para los
                'datos hidráulicos. Si no encuentra el dato invierte los nudos
                'falta controlar error si no encuentra el dato al invertir
                hidraulicosVerifica = ExcelSheet.cells(fila, colCaudal).Text
                If hidraulicosVerifica = "N/A" Then
                    ExcelSheet.cells(fila, colNudoInicio).Value = textoNudoInicio.TextString
                    ExcelSheet.cells(fila, colNudoFin).Value = textoNudoFin.TextString
                End If
                'Lee de Excel y ubica datos hidráulicos
                caudal = "Q= " & ExcelSheet.cells(fila, colCaudal).Text & " L/s"
                Set textoCad = ThisDrawing.ModelSpace.AddText(caudal, coordTextoGuia, altura)
                textoCad.Rotate GiroCaja, rotaGuia
                textoCad.Layer = capaDH
                textoCad.color = acYellow
                textoCad.StyleName = "Standard"
                
                coordTextoGuia(1) = coordTextoGuia(1) - salto
                velocidad = "V= " & ExcelSheet.cells(fila, colVelocidad).Value & " m/s"
                Set textoCad = ThisDrawing.ModelSpace.AddText(velocidad, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.51
                diametro = "DN= " & ExcelSheet.cells(fila, colDiametro).Value & " mm"
                Set textoCad = ThisDrawing.ModelSpace.AddText(diametro, coordTextoGuia, altura)
                textoCad.Rotate GiroCaja, rotaGuia
                textoCad.Layer = capaDH
                textoCad.color = acYellow
                textoCad.StyleName = "Standard"
                coordTextoGuia(0) = coordTextoGuiaAux
                
                coordTextoGuia(1) = coordTextoGuia(1) - salto
                longitud = "L= " & ExcelSheet.cells(fila, colLongitud).Value & " m"
                Set textoCad = ThisDrawing.ModelSpace.AddText(longitud, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.65
                material = ExcelSheet.cells(fila, colMaterial).Text
                Set textoCad = ThisDrawing.ModelSpace.AddText(material, coordTextoGuia, altura)
                textoCad.Rotate GiroCaja, rotaGuia
                textoCad.Layer = capaDH
                textoCad.color = acYellow
                textoCad.StyleName = "Standard"
                coordTextoGuia(0) = coordTextoGuiaAux
            Next op1
        Case 2:
            For j = filaI To filaF
                capaDH = ExcelSheet.cells(j, colCapa)
                
                'Controlar error cuando no encuentra el dato en la búsqueda para las
                'coordenadas donde se van a insertar el texto
                'si no encuentra el dato invierte los nudos.
                'Falta controlar error si no encuentra el dato al invertir
                nudoInicioAux = ExcelSheet.cells(j, colNudoInicio).Value
                nudoFinAux = ExcelSheet.cells(j, colNudoFin).Value
                coordenadasVerifica = ExcelSheet.cells(j, colTextoEste).Text
                If coordenadasVerifica = "#N/A" Then
                    ExcelSheet.cells(j, colNudoInicio).Value = nudoFinAux
                    ExcelSheet.cells(j, colNudoFin).Value = nudoInicioAux
                End If
                
                'Lee las coordenadas para insertar los datos hidráulicos
                coordTextoGuia(0) = ExcelSheet.cells(j, colTextoEste).Value
                coordTextoGuia(1) = ExcelSheet.cells(j, colTextoNorte).Value
                rotaGuia = ExcelSheet.cells(j, colOrientacion).Value
                GiroCaja(0) = coordTextoGuia(0): GiroCaja(1) = coordTextoGuia(1)
                
                'Controlar error cuando no se encuentra el dato en la búsqueda para los
                'datos hidráulicos. Si no encuentra el dato invierte los nudos
                'falta controlar error si no encuentra el dato al invertir
                hidraulicosVerifica = ExcelSheet.cells(j, colCaudal).Text
                nudoInicioAux = ExcelSheet.cells(j, colNudoInicio).Value
                nudoFinAux = ExcelSheet.cells(j, colNudoFin).Value
                If hidraulicosVerifica = "#N/A" Then
                    ExcelSheet.cells(j, colNudoInicio).Value = nudoFinAux
                    ExcelSheet.cells(j, colNudoFin).Value = nudoInicioAux
                End If
                
                'Ubica datos hidráulicos
                caudal = "Q= " & ExcelSheet.cells(j, colCaudal).Text & " L/s"
                Set textoCad = ThisDrawing.ModelSpace.AddText(caudal, coordTextoGuia, altura)
                textoCad.Rotate GiroCaja, rotaGuia
                textoCad.Layer = capaDH
                textoCad.color = acYellow
                textoCad.StyleName = "Standard"
                
                coordTextoGuia(1) = coordTextoGuia(1) - salto
                velocidad = "V= " & ExcelSheet.cells(j, colVelocidad).Value & " m/s"
                Set textoCad = ThisDrawing.ModelSpace.AddText(velocidad, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.51
                diametro = "DN= " & ExcelSheet.cells(j, colDiametro).Value & " mm"
                Set textoCad = ThisDrawing.ModelSpace.AddText(diametro, coordTextoGuia, altura)
                textoCad.Rotate GiroCaja, rotaGuia
                textoCad.Layer = capaDH
                textoCad.color = acYellow
                textoCad.StyleName = "Standard"
                coordTextoGuia(0) = coordTextoGuiaAux
                
                coordTextoGuia(1) = coordTextoGuia(1) - salto
                longitud = "L= " & ExcelSheet.cells(j, colLongitud).Value & " m"
                Set textoCad = ThisDrawing.ModelSpace.AddText(longitud, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.65
                material = ExcelSheet.cells(j, colMaterial).Text
                Set textoCad = ThisDrawing.ModelSpace.AddText(material, coordTextoGuia, altura)
                textoCad.Rotate GiroCaja, rotaGuia
                textoCad.Layer = capaDH
                textoCad.color = acYellow
                textoCad.StyleName = "Standard"
                coordTextoGuia(0) = coordTextoGuiaAux
                ExcelSheet.cells(j, 14).Interior.ColorIndex = 4
            Next j
    End Select
End Sub
'Enviar valor de 1 para filaI cuando se va a dibujar de forma individual
Sub insertarDatosNudosAP(ByVal formaDibujo As String)
    'Inserta datos hidráulicos de nudos en la red de agua potable
    'Toma los datos de Excel
    'Plan Maestro Tulcán
    
    FormDatosHid.Hide
    
    Dim Excel As Object
    Dim ExcelSheet As Object
    Dim ExcelWorkbook As Object
    
    Dim textoNudo As AcadText
    Dim textoHid As AcadText
        
    Dim coordTextoGuia(0 To 2) As Double
    
'    Dim formaDibujo As String
    Dim idNudo, zona, elevacion, presion As String
    Dim orientacion As Double
    Dim salto, altura As Double
    Dim colIdNudo, colElevacion, colPresion, colZona As Integer
    Dim colTextoEste, colTextoNorte, colOrientacion As Integer
    Dim filaI, filaF, fila As Integer
    
    'Habilita EXCEL
    Set Excel = GetObject(, "Excel.Application")
    ' Activa archivo de Excel y la hoja de trabajo abierta.
    Set ExcelWorkbook = Excel.ActiveWorkbook
    Excel.Sheets(3).Select
    Set ExcelSheet = Excel.ActiveSheet
    Set celdas = Excel.ActiveCell
    filaI = celdas.row
    
    salto = 1.75: altura = 1.5
    colIdNudo = 6: colElevacion = 7: colPresion = 8
    colZona = 9: colTextoEste = 11: colTextoNorte = 10
    
'    formaDibujo = InputBox("Forma de dibujar" & vbCrLf & "1. Individual" & vbCrLf & "2. Todo", "DIBUJO NUDOS", 1)
    If formaDibujo = 1 Then
        filaI = 1
        filaF = ThisDrawing.Utility.GetInteger("Número de nudos")
    Else
        filaI = InputBox("Fila inicio", "INICIO", filaI)
        filaF = InputBox("Fila final", "FIN", filaI + 1)
    End If
    fila = 3
    
'    On Error Resume Next
    Select Case formaDibujo
        Case 1:
            filaF = ThisDrawing.Utility.GetInteger("Número de nudos")
            For op1 = filaI To filaF
                ThisDrawing.Utility.GetEntity textoNudo, puntoRef, "<Picar nudo>"
                ExcelSheet.cells(fila, colIdNudo).Value = textoNudo.TextString
                zona = ExcelSheet.cells(fila, colZona).Text
                coordTextoGuia(0) = ExcelSheet.cells(fila, colTextoEste).Value
                coordTextoGuia(1) = ExcelSheet.cells(fila, colTextoNorte).Value
                
                'Ubica datos hidráulicos
                idNudo = ExcelSheet.cells(fila, colIdNudo).Text
                Set textoHid = ThisDrawing.ModelSpace.AddText(idNudo, coordTextoGuia, altura)
'                textoCad.Rotate coordTextoGuia, 0
                textoCad.Layer = zona
                textoCad.color = acRed
                textoCad.StyleName = "Standard"
                
                coordTextoGuia(1) = coordTextoGuia(1) - salto
                elevacion = ExcelSheet.cells(fila, colElevacion).Value & " m"
                Set textoHid = ThisDrawing.ModelSpace.AddText(elevacion, coordTextoGuia, altura)
'                textoCad.Rotate coordTextoGuia, 0
                textoCad.Layer = zona
                textoCad.color = acRed
                textoCad.StyleName = "Standard"
                
                coordTextoGuia(1) = coordTextoGuia(1) - salto
                presion = ExcelSheet.cells(fila, colPresion).Value & " mca"
                Set textoHid = ThisDrawing.ModelSpace.AddText(presion, coordTextoGuia, altura)
'                textoCad.Rotate coordTextoGuia, 0
                textoCad.Layer = zona
                textoCad.color = acRed
                textoCad.StyleName = "Standard"
            Next op1
        Case 2:
            For j = filaI To filaF
                zona = ExcelSheet.cells(j, colZona).Text
                coordTextoGuia(0) = ExcelSheet.cells(j, colTextoEste).Value
                coordTextoGuia(1) = ExcelSheet.cells(j, colTextoNorte).Value
                
                'Ubica datos hidráulicos
                idNudo = ExcelSheet.cells(j, colIdNudo).Text
                Set textoHid = ThisDrawing.ModelSpace.AddText(idNudo, coordTextoGuia, altura)
'                textoCad.Rotate coordTextoGuia, 0
                textoHid.Layer = zona
                textoHid.color = acRed
                textoHid.StyleName = "Standard"
                
                coordTextoGuia(1) = coordTextoGuia(1) - salto
                elevacion = "C= " & ExcelSheet.cells(j, colElevacion).Value & " m"
                Set textoHid = ThisDrawing.ModelSpace.AddText(elevacion, coordTextoGuia, altura)
'                textoCad.Rotate coordTextoGuia, 0
                textoHid.Layer = zona
                textoHid.color = acRed
                textoHid.StyleName = "Standard"
                
                coordTextoGuia(1) = coordTextoGuia(1) - salto
                presion = "P= " & ExcelSheet.cells(j, colPresion).Value & " mca"
                Set textoHid = ThisDrawing.ModelSpace.AddText(presion, coordTextoGuia, altura)
'                textoCad.Rotate coordTextoGuia, 0
                textoHid.Layer = zona
                textoHid.color = acRed
                textoHid.StyleName = "Standard"
                ExcelSheet.cells(j, colIdNudo).Interior.ColorIndex = 4
            Next j
    End Select
End Sub

Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Sub iniciarDatosHidAP()
    FormDatosHid.show
End Sub
