Attribute VB_Name = "Module1"
Sub insertarDatosTramosAP()
    'Inserta datos hidráulicos en tramos de tubería de agua potable
    'Toma los datos de un archivo de Excel
    'Plan Maestro Tulcán
        
    Dim Excel As Object
    Dim ExcelSheet As Object
    Dim ExcelWorkbook As Object
    
    Dim textoCad As AcadText
    Dim textoNudoInicio As AcadText
    Dim textoNudoFin As AcadText
    
    Dim coordTextoGuia(0 To 2) As Double
    Dim coordTextoGuiaAux As Double
    Dim lineaP2(0 To 2) As Double
    Dim GiroCaja(0 To 2) As Double
    
    Dim formaDibujo As String
    Dim caudal, velocidad, diametro As String
    Dim longitud, material As String
    Dim capaDH As String
    Dim RE, MC1, MC2, altura, salto As Double
    Dim rotaGuia As Double
    Dim filaI, filaF, fila As Integer
    
    Dim colNudoInicio, colNudoFin As Integer
    Dim colCaudal, colVelocidad, colDiametro, colLongitud As Integer
    Dim colMaterial, colTextoEste, colTextoNorte, colOrientacion As Integer
    Dim colCapa As Integer
    
    'Habilita EXCEL
    Set Excel = GetObject(, "Excel.Application")
    ' Activa archivo de Excel y la hoja de trabajo abierta.
    Set ExcelWorkbook = Excel.ActiveWorkbook
    Set ExcelSheet = Excel.ActiveSheet
    Set celdas = Excel.ActiveCell
    filaI = celdas.row
    
    salto = 1.75
    RE = escala / 1000
    MC1 = -3 * RE 'Cambio 6 por 2
    MC2 = 1.5 * RE 'y 14 por 10
    altura = 1.5
    
    colNudoInicio = 12: colNudoFin = 13
    colCaudal = 15: colVelocidad = 16: colDiametro = 17: colLongitud = 18
    colMaterial = 19: colTextoEste = 20: colTextoNorte = 21: colOrientacion = 22
    colCapa = 23
    
    formaDibujo = InputBox("Forma de dibujar" & vbCrLf & "1. Por tramos" & vbCrLf & "2. Todo", "DIBUJO TRAMOS", 1)
    If formaDibujo = 1 Then
        filaI = 1
        filaF = ThisDrawing.Utility.GetInteger("Número de tramos")
    Else
        filaI = InputBox("Fila inicio", "INICIO", filaI)
        filaF = InputBox("Fila final", "FIN")
    End If
    fila = 3
    On Error Resume Next
    
    Select Case formaDibujo
        Case 1:
            For op1 = filaI To filaF
                ThisDrawing.Utility.GetEntity textoNudoInicio, puntoRef, "<Marcar texto nudo inicio: >: "
                ExcelSheet.cells(fila, colNudoInicio).Value = textoNudoInicio.TextString
                ThisDrawing.Utility.GetEntity textoNudoFin, puntoRef, "<Marcar texto nudo fin: >: "
                ExcelSheet.cells(fila, colNudoFin).Value = textoNudoFin.TextString
                'Lee del Excel datos para ubicar los datos
                capaDH = ExcelSheet.cells(fila, colCapa)
                rotaGuia = ExcelSheet.cells(fila, colOrientacion).Value
                
                coordTextoGuia(0) = ExcelSheet.cells(fila, colTextoEste).Value
                coordTextoGuia(1) = ExcelSheet.cells(fila, colTextoNorte).Value
                GiroCaja(0) = coordTextoGuia(0): GiroCaja(1) = coordTextoGuia(1)
                
                'Ubica datos hidráulicos
                caudal = "Q= " & ExcelSheet.cells(fila, colCaudal).text & " L/s"
                Set textoCad = ThisDrawing.ModelSpace.AddText(caudal, coordTextoGuia, altura)
                textoCad.Rotate GiroCaja, rotaGuia
                textoCad.Layer = capaDH
                textoCad.color = acYellow
                textoCad.StyleName = "Standard"
                
                coordTextoGuia(1) = coordTextoGuia(1) - salto
                velocidad = "V= " & ExcelSheet.cells(fila, colVelocidad).Value & " m/s"
                Set textoCad = ThisDrawing.ModelSpace.AddText(velocidad, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.51
                diametro = "DN= " & ExcelSheet.cells(fila, colDiametro).Value & " mm"
                Set textoCad = ThisDrawing.ModelSpace.AddText(diametro, coordTextoGuia, altura)
                textoCad.Rotate GiroCaja, rotaGuia
                textoCad.Layer = capaDH
                textoCad.color = acYellow
                textoCad.StyleName = "Standard"
                coordTextoGuia(0) = coordTextoGuiaAux
                
                coordTextoGuia(1) = coordTextoGuia(1) - salto
                longitud = "L= " & ExcelSheet.cells(fila, colLongitud).Value & " m"
                Set textoCad = ThisDrawing.ModelSpace.AddText(longitud, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.65
                material = ExcelSheet.cells(fila, colMaterial).text
                Set textoCad = ThisDrawing.ModelSpace.AddText(material, coordTextoGuia, altura)
                textoCad.Rotate GiroCaja, rotaGuia
                textoCad.Layer = capaDH
                textoCad.color = acYellow
                textoCad.StyleName = "Standard"
                coordTextoGuia(0) = coordTextoGuiaAux
            Next op1
        Case 2:
            For j = filaI To filaF
                capaDH = ExcelSheet.cells(j, colCapa)
                rotaGuia = ExcelSheet.cells(j, colOrientacion).Value
                
                coordTextoGuia(0) = ExcelSheet.cells(j, colTextoEste).Value
                coordTextoGuia(1) = ExcelSheet.cells(j, colTextoNorte).Value
                GiroCaja(0) = coordTextoGuia(0): GiroCaja(1) = coordTextoGuia(1)
                
                'Ubica datos hidráulicos
                caudal = "Q= " & ExcelSheet.cells(j, colCaudal).text & " L/s"
                Set textoCad = ThisDrawing.ModelSpace.AddText(caudal, coordTextoGuia, altura)
                textoCad.Rotate GiroCaja, rotaGuia
                textoCad.Layer = capaDH
                textoCad.color = acYellow
                textoCad.StyleName = "Standard"
                
                coordTextoGuia(1) = coordTextoGuia(1) - salto
                velocidad = "V= " & ExcelSheet.cells(j, colVelocidad).Value & " m/s"
                Set textoCad = ThisDrawing.ModelSpace.AddText(velocidad, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.51
                diametro = "DN= " & ExcelSheet.cells(j, colDiametro).Value & " mm"
                Set textoCad = ThisDrawing.ModelSpace.AddText(diametro, coordTextoGuia, altura)
                textoCad.Rotate GiroCaja, rotaGuia
                textoCad.Layer = capaDH
                textoCad.color = acYellow
                textoCad.StyleName = "Standard"
                coordTextoGuia(0) = coordTextoGuiaAux
                
                coordTextoGuia(1) = coordTextoGuia(1) - salto
                longitud = "L= " & ExcelSheet.cells(j, colLongitud).Value & " m"
                Set textoCad = ThisDrawing.ModelSpace.AddText(longitud, coordTextoGuia, altura)
                textoCad.Rotate GiroCaja, rotaGuia
                textoCad.Layer = capaDH
                textoCad.color = acYellow
                textoCad.StyleName = "Standard"
                
                coordTextoGuia(1) = coordTextoGuia(1) - salto
                coordTextoGuiaAux = coordTextoGuia(0)
                coordTextoGuia(0) = coordTextoGuia(0) - 1.65
                material = ExcelSheet.cells(j, colMaterial).text
                Set textoCad = ThisDrawing.ModelSpace.AddText(material, coordTextoGuia, altura)
                textoCad.Rotate GiroCaja, rotaGuia
                textoCad.Layer = capaDH
                textoCad.color = acYellow
                textoCad.StyleName = "Standard"
                coordTextoGuia(0) = coordTextoGuiaAux
                ExcelSheet.cells(j, 14).Interior.ColorIndex = 4
            Next j
    End Select
'    For j = filaI To filaF
'        If Xtramo = 1 Then
'
'        Else
''            ExcelSheet.cells(fila, colNudoInicio).Value = ExcelSheet.cells(j, 1).Value
''            ExcelSheet.cells(fila, colNudoFin).Value = ExcelSheet.cells(j + 1, 1).Value
'
'            'Lee del Excel datos para ubicar los datos
'
'        End If
'    Next j
End Sub
